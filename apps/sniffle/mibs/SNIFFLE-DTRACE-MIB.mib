SNIFFLE-DTRACE-MIB DEFINITIONS ::= BEGIN

    IMPORTS
        experimental   FROM RFC1155-SMI
        OBJECT-TYPE    FROM RFC-1212
        sniffle        FROM SNIFFLE-MIB
        ;

    dtrace   OBJECT IDENTIFIER ::= { sniffle  2 }

-- Hypervisor Section
    readP999 OBJECT-TYPE
        SYNTAX  INTEGER
        ACCESS  read-only
        STATUS  mandatory
        DESCRIPTION
            "99.9 percertile"
        ::= { dtrace 1 }

    readP99 OBJECT-TYPE
        SYNTAX  INTEGER
        ACCESS  read-only
        STATUS  mandatory
        DESCRIPTION
            "99 percertile"
        ::= { dtrace 2 }

    readP95 OBJECT-TYPE
        SYNTAX  INTEGER
        ACCESS  read-only
        STATUS  mandatory
        DESCRIPTION
            "95 percertile"
        ::= { dtrace 3 }

    readP75 OBJECT-TYPE
        SYNTAX  INTEGER
        ACCESS  read-only
        STATUS  mandatory
        DESCRIPTION
            "75 percertile"
        ::= { dtrace 4 }

    readP25 OBJECT-TYPE
        SYNTAX  INTEGER
        ACCESS  read-only
        STATUS  mandatory
        DESCRIPTION
            "25 percertile"
        ::= { dtrace 5 }

    readCount OBJECT-TYPE
        SYNTAX  INTEGER
        ACCESS  read-only
        STATUS  mandatory
        DESCRIPTION
            "number of events"
        ::= { dtrace 6 }

    readMin OBJECT-TYPE
        SYNTAX  INTEGER
        ACCESS  read-only
        STATUS  mandatory
        DESCRIPTION
            "number of events"
        ::= { dtrace 7 }

    readMedian OBJECT-TYPE
        SYNTAX  INTEGER
        ACCESS  read-only
        STATUS  mandatory
        DESCRIPTION
            "number of events"
        ::= { dtrace 8 }

    readMean OBJECT-TYPE
        SYNTAX  INTEGER
        ACCESS  read-only
        STATUS  mandatory
        DESCRIPTION
            "number of events"
        ::= { dtrace 9 }

    readMax OBJECT-TYPE
        SYNTAX  INTEGER
        ACCESS  read-only
        STATUS  mandatory
        DESCRIPTION
            "number of events"
        ::= { dtrace 10 }

    writeP999 OBJECT-TYPE
        SYNTAX  INTEGER
        ACCESS  read-only
        STATUS  mandatory
        DESCRIPTION
            "99.9 percertile"
        ::= { dtrace 11 }

    writeP99 OBJECT-TYPE
        SYNTAX  INTEGER
        ACCESS  read-only
        STATUS  mandatory
        DESCRIPTION
            "99 percertile"
        ::= { dtrace 12 }

    writeP95 OBJECT-TYPE
        SYNTAX  INTEGER
        ACCESS  read-only
        STATUS  mandatory
        DESCRIPTION
            "95 percertile"
        ::= { dtrace 13 }

    writeP75 OBJECT-TYPE
        SYNTAX  INTEGER
        ACCESS  read-only
        STATUS  mandatory
        DESCRIPTION
            "75 percertile"
        ::= { dtrace 14 }

    writeP25 OBJECT-TYPE
        SYNTAX  INTEGER
        ACCESS  read-only
        STATUS  mandatory
        DESCRIPTION
            "25 percertile"
        ::= { dtrace 15 }

    writeCount OBJECT-TYPE
        SYNTAX  INTEGER
        ACCESS  read-only
        STATUS  mandatory
        DESCRIPTION
            "number of events"
        ::= { dtrace 16 }

    writeMin OBJECT-TYPE
        SYNTAX  INTEGER
        ACCESS  read-only
        STATUS  mandatory
        DESCRIPTION
            "number of events"
        ::= { dtrace 17 }

    writeMedian OBJECT-TYPE
        SYNTAX  INTEGER
        ACCESS  read-only
        STATUS  mandatory
        DESCRIPTION
            "number of events"
        ::= { dtrace 18 }

    writeMean OBJECT-TYPE
        SYNTAX  INTEGER
        ACCESS  read-only
        STATUS  mandatory
        DESCRIPTION
            "number of events"
        ::= { dtrace 19 }

    writeMax OBJECT-TYPE
        SYNTAX  INTEGER
        ACCESS  read-only
        STATUS  mandatory
        DESCRIPTION
            "number of events"
        ::= { dtrace 20 }

    listP999 OBJECT-TYPE
        SYNTAX  INTEGER
        ACCESS  read-only
        STATUS  mandatory
        DESCRIPTION
            "99.9 percertile"
        ::= { dtrace 21 }

    listP99 OBJECT-TYPE
        SYNTAX  INTEGER
        ACCESS  read-only
        STATUS  mandatory
        DESCRIPTION
            "99 percertile"
        ::= { dtrace 22 }

    listP95 OBJECT-TYPE
        SYNTAX  INTEGER
        ACCESS  read-only
        STATUS  mandatory
        DESCRIPTION
            "95 percertile"
        ::= { dtrace 23 }

    listP75 OBJECT-TYPE
        SYNTAX  INTEGER
        ACCESS  read-only
        STATUS  mandatory
        DESCRIPTION
            "75 percertile"
        ::= { dtrace 24 }

    listP25 OBJECT-TYPE
        SYNTAX  INTEGER
        ACCESS  read-only
        STATUS  mandatory
        DESCRIPTION
            "25 percertile"
        ::= { dtrace 25 }

    listCount OBJECT-TYPE
        SYNTAX  INTEGER
        ACCESS  read-only
        STATUS  mandatory
        DESCRIPTION
            "number of events"
        ::= { dtrace 26 }

    listMin OBJECT-TYPE
        SYNTAX  INTEGER
        ACCESS  read-only
        STATUS  mandatory
        DESCRIPTION
            "number of events"
        ::= { dtrace 27 }

    listMedian OBJECT-TYPE
        SYNTAX  INTEGER
        ACCESS  read-only
        STATUS  mandatory
        DESCRIPTION
            "number of events"
        ::= { dtrace 28 }

    listMean OBJECT-TYPE
        SYNTAX  INTEGER
        ACCESS  read-only
        STATUS  mandatory
        DESCRIPTION
            "number of events"
        ::= { dtrace 29 }

    listMax OBJECT-TYPE
        SYNTAX  INTEGER
        ACCESS  read-only
        STATUS  mandatory
        DESCRIPTION
            "number of events"
        ::= { dtrace 30 }

    repairP999 OBJECT-TYPE
        SYNTAX  INTEGER
        ACCESS  read-only
        STATUS  mandatory
        DESCRIPTION
            "99.9 percertile"
        ::= { dtrace 31 }

    repairP99 OBJECT-TYPE
        SYNTAX  INTEGER
        ACCESS  read-only
        STATUS  mandatory
        DESCRIPTION
            "99 percertile"
        ::= { dtrace 32 }

    repairP95 OBJECT-TYPE
        SYNTAX  INTEGER
        ACCESS  read-only
        STATUS  mandatory
        DESCRIPTION
            "95 percertile"
        ::= { dtrace 33 }

    repairP75 OBJECT-TYPE
        SYNTAX  INTEGER
        ACCESS  read-only
        STATUS  mandatory
        DESCRIPTION
            "75 percertile"
        ::= { dtrace 34 }

    repairP25 OBJECT-TYPE
        SYNTAX  INTEGER
        ACCESS  read-only
        STATUS  mandatory
        DESCRIPTION
            "25 percertile"
        ::= { dtrace 35 }

    repairCount OBJECT-TYPE
        SYNTAX  INTEGER
        ACCESS  read-only
        STATUS  mandatory
        DESCRIPTION
            "number of events"
        ::= { dtrace 36 }

    repairMin OBJECT-TYPE
        SYNTAX  INTEGER
        ACCESS  read-only
        STATUS  mandatory
        DESCRIPTION
            "number of events"
        ::= { dtrace 37 }

    repairMedian OBJECT-TYPE
        SYNTAX  INTEGER
        ACCESS  read-only
        STATUS  mandatory
        DESCRIPTION
            "number of events"
        ::= { dtrace 38 }

    repairMean OBJECT-TYPE
        SYNTAX  INTEGER
        ACCESS  read-only
        STATUS  mandatory
        DESCRIPTION
            "number of events"
        ::= { dtrace 39 }

    repairMax OBJECT-TYPE
        SYNTAX  INTEGER
        ACCESS  read-only
        STATUS  mandatory
        DESCRIPTION
            "number of events"
        ::= { dtrace 40 }
END
