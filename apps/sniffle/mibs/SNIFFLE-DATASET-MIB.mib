SNIFFLE-DATASET-MIB DEFINITIONS ::= BEGIN

    IMPORTS
        experimental   FROM RFC1155-SMI
        OBJECT-TYPE    FROM RFC-1212
        sniffle        FROM SNIFFLE-MIB
        ;

    dataset   OBJECT IDENTIFIER ::= { sniffle  2 }

-- Hypervisor Section
    readP999 OBJECT-TYPE
        SYNTAX  INTEGER
        ACCESS  read-only
        STATUS  mandatory
        DESCRIPTION
            "99.9 percertile"
        ::= { dataset 1 }

    readP99 OBJECT-TYPE
        SYNTAX  INTEGER
        ACCESS  read-only
        STATUS  mandatory
        DESCRIPTION
            "99 percertile"
        ::= { dataset 2 }

    readP95 OBJECT-TYPE
        SYNTAX  INTEGER
        ACCESS  read-only
        STATUS  mandatory
        DESCRIPTION
            "95 percertile"
        ::= { dataset 3 }

    readP75 OBJECT-TYPE
        SYNTAX  INTEGER
        ACCESS  read-only
        STATUS  mandatory
        DESCRIPTION
            "75 percertile"
        ::= { dataset 4 }

    readP25 OBJECT-TYPE
        SYNTAX  INTEGER
        ACCESS  read-only
        STATUS  mandatory
        DESCRIPTION
            "25 percertile"
        ::= { dataset 5 }

    readCount OBJECT-TYPE
        SYNTAX  INTEGER
        ACCESS  read-only
        STATUS  mandatory
        DESCRIPTION
            "number of events"
        ::= { dataset 6 }

    readMin OBJECT-TYPE
        SYNTAX  INTEGER
        ACCESS  read-only
        STATUS  mandatory
        DESCRIPTION
            "number of events"
        ::= { dataset 7 }

    readMedian OBJECT-TYPE
        SYNTAX  INTEGER
        ACCESS  read-only
        STATUS  mandatory
        DESCRIPTION
            "number of events"
        ::= { dataset 8 }

    readMean OBJECT-TYPE
        SYNTAX  INTEGER
        ACCESS  read-only
        STATUS  mandatory
        DESCRIPTION
            "number of events"
        ::= { dataset 9 }

    readMax OBJECT-TYPE
        SYNTAX  INTEGER
        ACCESS  read-only
        STATUS  mandatory
        DESCRIPTION
            "number of events"
        ::= { dataset 10 }

    writeP999 OBJECT-TYPE
        SYNTAX  INTEGER
        ACCESS  read-only
        STATUS  mandatory
        DESCRIPTION
            "99.9 percertile"
        ::= { dataset 11 }

    writeP99 OBJECT-TYPE
        SYNTAX  INTEGER
        ACCESS  read-only
        STATUS  mandatory
        DESCRIPTION
            "99 percertile"
        ::= { dataset 12 }

    writeP95 OBJECT-TYPE
        SYNTAX  INTEGER
        ACCESS  read-only
        STATUS  mandatory
        DESCRIPTION
            "95 percertile"
        ::= { dataset 13 }

    writeP75 OBJECT-TYPE
        SYNTAX  INTEGER
        ACCESS  read-only
        STATUS  mandatory
        DESCRIPTION
            "75 percertile"
        ::= { dataset 14 }

    writeP25 OBJECT-TYPE
        SYNTAX  INTEGER
        ACCESS  read-only
        STATUS  mandatory
        DESCRIPTION
            "25 percertile"
        ::= { dataset 15 }

    writeCount OBJECT-TYPE
        SYNTAX  INTEGER
        ACCESS  read-only
        STATUS  mandatory
        DESCRIPTION
            "number of events"
        ::= { dataset 16 }

    writeMin OBJECT-TYPE
        SYNTAX  INTEGER
        ACCESS  read-only
        STATUS  mandatory
        DESCRIPTION
            "number of events"
        ::= { dataset 17 }

    writeMedian OBJECT-TYPE
        SYNTAX  INTEGER
        ACCESS  read-only
        STATUS  mandatory
        DESCRIPTION
            "number of events"
        ::= { dataset 18 }

    writeMean OBJECT-TYPE
        SYNTAX  INTEGER
        ACCESS  read-only
        STATUS  mandatory
        DESCRIPTION
            "number of events"
        ::= { dataset 19 }

    writeMax OBJECT-TYPE
        SYNTAX  INTEGER
        ACCESS  read-only
        STATUS  mandatory
        DESCRIPTION
            "number of events"
        ::= { dataset 20 }

    listP999 OBJECT-TYPE
        SYNTAX  INTEGER
        ACCESS  read-only
        STATUS  mandatory
        DESCRIPTION
            "99.9 percertile"
        ::= { dataset 21 }

    listP99 OBJECT-TYPE
        SYNTAX  INTEGER
        ACCESS  read-only
        STATUS  mandatory
        DESCRIPTION
            "99 percertile"
        ::= { dataset 22 }

    listP95 OBJECT-TYPE
        SYNTAX  INTEGER
        ACCESS  read-only
        STATUS  mandatory
        DESCRIPTION
            "95 percertile"
        ::= { dataset 23 }

    listP75 OBJECT-TYPE
        SYNTAX  INTEGER
        ACCESS  read-only
        STATUS  mandatory
        DESCRIPTION
            "75 percertile"
        ::= { dataset 24 }

    listP25 OBJECT-TYPE
        SYNTAX  INTEGER
        ACCESS  read-only
        STATUS  mandatory
        DESCRIPTION
            "25 percertile"
        ::= { dataset 25 }

    listCount OBJECT-TYPE
        SYNTAX  INTEGER
        ACCESS  read-only
        STATUS  mandatory
        DESCRIPTION
            "number of events"
        ::= { dataset 26 }

    listMin OBJECT-TYPE
        SYNTAX  INTEGER
        ACCESS  read-only
        STATUS  mandatory
        DESCRIPTION
            "number of events"
        ::= { dataset 27 }

    listMedian OBJECT-TYPE
        SYNTAX  INTEGER
        ACCESS  read-only
        STATUS  mandatory
        DESCRIPTION
            "number of events"
        ::= { dataset 28 }

    listMean OBJECT-TYPE
        SYNTAX  INTEGER
        ACCESS  read-only
        STATUS  mandatory
        DESCRIPTION
            "number of events"
        ::= { dataset 29 }

    listMax OBJECT-TYPE
        SYNTAX  INTEGER
        ACCESS  read-only
        STATUS  mandatory
        DESCRIPTION
            "number of events"
        ::= { dataset 30 }

    repairP999 OBJECT-TYPE
        SYNTAX  INTEGER
        ACCESS  read-only
        STATUS  mandatory
        DESCRIPTION
            "99.9 percertile"
        ::= { dataset 31 }

    repairP99 OBJECT-TYPE
        SYNTAX  INTEGER
        ACCESS  read-only
        STATUS  mandatory
        DESCRIPTION
            "99 percertile"
        ::= { dataset 32 }

    repairP95 OBJECT-TYPE
        SYNTAX  INTEGER
        ACCESS  read-only
        STATUS  mandatory
        DESCRIPTION
            "95 percertile"
        ::= { dataset 33 }

    repairP75 OBJECT-TYPE
        SYNTAX  INTEGER
        ACCESS  read-only
        STATUS  mandatory
        DESCRIPTION
            "75 percertile"
        ::= { dataset 34 }

    repairP25 OBJECT-TYPE
        SYNTAX  INTEGER
        ACCESS  read-only
        STATUS  mandatory
        DESCRIPTION
            "25 percertile"
        ::= { dataset 35 }

    repairCount OBJECT-TYPE
        SYNTAX  INTEGER
        ACCESS  read-only
        STATUS  mandatory
        DESCRIPTION
            "number of events"
        ::= { dataset 36 }

    repairMin OBJECT-TYPE
        SYNTAX  INTEGER
        ACCESS  read-only
        STATUS  mandatory
        DESCRIPTION
            "number of events"
        ::= { dataset 37 }

    repairMedian OBJECT-TYPE
        SYNTAX  INTEGER
        ACCESS  read-only
        STATUS  mandatory
        DESCRIPTION
            "number of events"
        ::= { dataset 38 }

    repairMean OBJECT-TYPE
        SYNTAX  INTEGER
        ACCESS  read-only
        STATUS  mandatory
        DESCRIPTION
            "number of events"
        ::= { dataset 39 }

    repairMax OBJECT-TYPE
        SYNTAX  INTEGER
        ACCESS  read-only
        STATUS  mandatory
        DESCRIPTION
            "number of events"
        ::= { dataset 40 }
END
